/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MessagePassingSEooC

import ScoreReq

///////////////////////////////
// Feature Requirements
// Integration level requirements derived from Assumed System Requirements
///////////////////////////////

ScoreReq.FeatReq ServerInterface {
    description = "The message passing component shall provide a server interface that registers connection handlers and processes incoming requests."
    safety = ScoreReq.Asil.B
    derived_from = [MessagePassingSEooC.SystemMessagingProtocol@1]
    version = 1
}

ScoreReq.FeatReq OSIndependentAPI {
    description = "The system shall provide an OS-independent API for OS-native IPC mechanisms."
    safety = ScoreReq.Asil.B
    derived_from = [MessagePassingSEooC.SystemMessagingProtocol@1]
    version = 1
}

ScoreReq.FeatReq SafetyCertifiedTransportMechanism {
    description = "The implementation under QNX shall use a safety-certified transport mechanism."
    safety = ScoreReq.Asil.B
    derived_from = [MessagePassingSEooC.SystemMessagingProtocol@1]
    version = 1
}

ScoreReq.FeatReq PointToPointConnections {
    description = "The system shall support only point-to-point (1:1) connections between communication endpoints. N:M connections are explicitly excluded."
    safety = ScoreReq.Asil.B
    derived_from = [MessagePassingSEooC.SystemMessagingProtocol@1]
    version = 1
}

ScoreReq.FeatReq SmallDataLowLatencyCommunication {
    description = "The system shall be optimized for the usage of small data and enable low-latency inter-process communication between dedicated endpoints."
    safety = ScoreReq.Asil.QM
    derived_from = [MessagePassingSEooC.SystemMessagingProtocol@1]
    version = 1
}

ScoreReq.FeatReq UnidirectionalAndTwoWayCommunicationModes {
    description = "The communication shall support unidirectional and two-way communication."
    safety = ScoreReq.Asil.B
    derived_from = [MessagePassingSEooC.SystemMessagingProtocol@1]
    version = 1
}

ScoreReq.FeatReq SynchronousAndAsynchronousCommunicationModes {
    description = "The communication shall support synchronous and asynchronous communication."
    safety = ScoreReq.Asil.B
    derived_from = [MessagePassingSEooC.SystemMessagingProtocol@1]
    version = 1
}
